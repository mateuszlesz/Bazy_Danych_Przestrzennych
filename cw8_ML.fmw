FME workspace cw8_ML.fmw

Parameters:
- SourceDataset_SHAPEFILE = $(FME_MF_DIR)Dane\T2019_KAR_POI_TABLE.shp   # Source Esri Shapefile(s)
- SourceDataset_SHAPEFILE_4 = $(FME_MF_DIR)Dane\T2019_KAR_STREET_NODE.shp   # Source Esri Shapefile(s)
- SourceDataset_SHAPEFILE_5 = $(FME_MF_DIR)Dane\T2019_KAR_STREETS.shp   # Source Esri Shapefile(s)
- FEATURE_TYPES = T2019_KAR_STREETS
- DestDataset_GEOJSON = $(FME_MF_DIR)buffor_POI.json   # Destination GeoJSON File
- DestDataset_GEOJSON_3 = $(FME_MF_DIR)buffor_POI_cost.json   # Destination GeoJSON File
- SourceDataset_CSV2_4 = $(FME_MF_DIR)Dane\plik.csv   # Source CSV (Comma Separated Value) File(s)
- DestDataset_FILEGDB = statystyki   # File Geodatabase

Readers:
- SHAPEFILE_1: SHAPEFILE from $(SourceDataset_SHAPEFILE) in LL-WGS84
- SHAPEFILE_2: SHAPEFILE from $(SourceDataset_SHAPEFILE_4) in LL-WGS84
- SHAPEFILE_3: SHAPEFILE from $(SourceDataset_SHAPEFILE_5) in LL-WGS84
- CSV2_2: CSV2 from $(SourceDataset_CSV2_4)

Writers:
- GEOJSON_1: GEOJSON to $(DestDataset_GEOJSON)
- GEOJSON_2: GEOJSON to $(DestDataset_GEOJSON_3)
- FILEGDB_1: FILEGDB to $(DestDataset_FILEGDB) in DHDN.Berlin/Cassini

T2019_KAR_POI_TABLE (reader SHAPEFILE_1)
    attributes: POI_ID long, LINK_ID long, TYPE char(250), POI_NAME char(250), ST_NAME char(250), LAT double, LON double
    -> Reprojector
Reprojector
    DEST = DHDN.Berlin/Cassini
    INTERPOLATION_TYPE_NAME = Nearest Neighbor
    RASTER_CELL_SIZE = Preserve Cells
    RASTER_TOLERANCE = 0.0
    SOURCE = Read from feature
    REPROJECTED -> SpatialFilterLength [Candidate]
    REPROJECTED -> SpatialFilter_length_costs [Candidate]
T2019_KAR_STREETS (reader SHAPEFILE_3)
    attributes: LINK_ID long, ST_NAME char(254), REF_IN_ID long, NREF_IN_ID long, FUNC_CLASS char(1), SPEED_CAT char(1), FR_SPEED_L long, TO_SPEED_L long, DIR_TRAVEL char(1)
    -> Reprojector_2
Reprojector_2
    DEST = DHDN.Berlin/Cassini
    INTERPOLATION_TYPE_NAME = Nearest Neighbor
    RASTER_CELL_SIZE = Preserve Cells
    RASTER_TOLERANCE = 0.0
    SOURCE = Read from feature
    REPROJECTED -> TestFilter
TestFilter
    DEFAULT_VALUE = <UNFILTERED>
    TEST_LIST = "BOOL_OP,OR,COMPOSITE_TEST,""""""1"""""",TEST_CLAUSE,CASE_INSENSITIVE_TEST @Value(DIR_TRAVEL) LIKE F",F(do przodu),"BOOL_OP,OR,COMPOSITE_TEST,""""""1"""""",TEST_CLAUSE,CASE_INSENSITIVE_TEST @Value(DIR_TRAVEL) LIKE B",B(dwukierunkowa),"BOOL_OP,OR,COMPOSITE_TEST,""""""1"""""",TEST_CLAUSE,CASE_INSENSITIVE_TEST @Value(DIR_TRAVEL) LIKE T",T(pod prad)
    F(do przodu) -> F
    B(dwukierunkowa) -> B
    T(pod prad) -> T
F: AttributeManager
    ATTR_TABLE:
      SET_TO ForwardCost = @Evaluate(1*@Length())
      SET_TO ReverseCost = @Evaluate(9999*@Length())
    -> Length_costs [NETWORK]
    -> Length [NETWORK]
B: AttributeManager
    ATTR_TABLE:
      SET_TO ForwardCost = @Evaluate(1*@Length())
      SET_TO ReverseCost = @Evaluate(1*@Length())
    -> Length_costs [NETWORK]
    -> Length [NETWORK]
T: AttributeManager
    ATTR_TABLE:
      SET_TO shapefile_type
      SET_TO ForwardCost = @Evaluate(9999*@Length())
      SET_TO ReverseCost = @Evaluate(1*@Length())
    -> Length_costs [NETWORK]
    -> Length [NETWORK]
CSV (reader CSV2_2)
    attributes: LAT y_coordinate, LON x_coordinate
    -> LineBuilder
LineBuilder
    ACCUM_INPUT_ATTRS = Use Attributes From One Feature
    REMOVE_DUPLICATES = No
    LINE -> Reprojector_4
Reprojector_4
    DEST = DHDN.Berlin/Cassini
    INTERPOLATION_TYPE_NAME = Nearest Neighbor
    RASTER_CELL_SIZE = Preserve Cells
    RASTER_TOLERANCE = 0.0
    SOURCE = Read from feature
    REPROJECTED -> Length_costs [FROM-TO]
    REPROJECTED -> Length [FROM-TO]
Length: ShortestPathFinder
    ALLOW_UTURNS = Yes
    REORDER_CHOICE = None
    SNAP_POINTS = Yes
    SNAP_TOLERANCE = 100
    WEIGHT_ATTR_CHOICE = By Length
    PATH -> Bufferer_length
    PATH -> FeatureMerger_lenght [SUPPLIER]
Bufferer_length
    ANGLE = 22.5
    CAP_STYLE = Round
    CORNER_STYLE = Round
    MODE = AREA
    OFFSET = 5
    OFFSET_UNITS = METERS
    PRECISION = APPROX
    BUFFERED -> SpatialFilterLength [Filter]
SpatialFilterLength
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> geoJSON_POI (writer GEOJSON_1)
    PASSED -> FeatureMerger_lenght [REQUESTOR]
geoJSON_POI (writer GEOJSON_1)
    attributes: LAT float, LON float, _total_cost string, POI_ID int, LINK_ID int, TYPE string, POI_NAME string, ST_NAME string, _predicate string
FeatureMerger_lenght
    ATTR_ACCUM_MODE = Merge Supplier
    ATTR_CONFLICT_RES = Use Requestor
    IGNORE_NULLS = No
    JOIN_KEYS = @Value(_total_cost) @Value(_total_cost) AUTO
    MERGE_TYPE = Attributes Only
    PROCESS_DUPS = NO
    REJECT_NULL_MISSING_KEYS = No
    SUPPLIERS_FIRST = No
    USED_SUPPLIER -> AttributeManager_length_2
AttributeManager_length_2
    ATTR_TABLE:
      SET_TO _length = @Length()
      SET_TO lenghtPERnoi = @div(@Value(_length),@Value(numReferences))
      SET_TO nazwa = Length
    -> AttributeRenamer
AttributeRenamer
    ATTR_TABLE = RENAME_SET_DEFAULT numReferences > noi_count
    -> statystyki (writer FILEGDB_1)
Length_costs: ShortestPathFinder
    ALLOW_UTURNS = Yes
    REORDER_CHOICE = None
    SNAP_POINTS = Yes
    SNAP_TOLERANCE = 100
    WEIGHT_ATTR_1 = ForwardCost
    WEIGHT_ATTR_2 = ReverseCost
    WEIGHT_ATTR_CHOICE = By Two Attributes
    PATH -> Bufferer_length_and_costs
    PATH -> FeatureMerger_length_costs [SUPPLIER]
Bufferer_length_and_costs
    ANGLE = 22.5
    CAP_STYLE = Round
    CORNER_STYLE = Round
    MODE = AREA
    OFFSET = 5
    OFFSET_UNITS = METERS
    PRECISION = APPROX
    BUFFERED -> SpatialFilter_length_costs [Filter]
SpatialFilter_length_costs
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> geoJSON_POI_cost (writer GEOJSON_2)
    PASSED -> FeatureMerger_length_costs [REQUESTOR]
FeatureMerger_length_costs
    ATTR_ACCUM_MODE = Merge Supplier
    ATTR_CONFLICT_RES = Use Requestor
    IGNORE_NULLS = No
    JOIN_KEYS = @Value(_total_cost) @Value(_total_cost) AUTO
    MERGE_TYPE = Attributes Only
    PROCESS_DUPS = NO
    REJECT_NULL_MISSING_KEYS = No
    SUPPLIERS_FIRST = No
    USED_SUPPLIER -> AttributeManager_length_costs
AttributeManager_length_costs
    ATTR_TABLE:
      SET_TO _length = @Length()
      SET_TO lenghtPERnoi = @div(@Value(_length),@Value(numReferences))
      SET_TO nazwa = Length&Costs
    -> AttributeRenamer_2
AttributeRenamer_2
    ATTR_TABLE = RENAME_SET_DEFAULT numReferences > noi_count
    -> statystyki (writer FILEGDB_1)
statystyki (writer FILEGDB_1)
    attributes: nazwa text(200), LAT double, LON double, _total_cost text(2048), _length text(200), noi_count text(200), lenghtPERnoi text(200)
geoJSON_POI_cost (writer GEOJSON_2)
    attributes: LAT float, LON float, _total_cost string, POI_ID int, LINK_ID int, TYPE string, POI_NAME string, ST_NAME string, _predicate string
